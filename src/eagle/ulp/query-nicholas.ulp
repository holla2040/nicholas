#include "auth.txt"; // sets DB* variables below
void alert(string s) {
    dlgMessageBox(s);
}

if (argc == 1) {
  alert("Usage: argv[0] searchstr");
}


string str_replace(string search, string replace, string subject) {
    int lastpos = 0;
    while(strstr(subject, search, lastpos) >= 0) {
        int pos = strstr(subject, search, lastpos);
        string before = strsub(subject, 0, pos);
        string after = strsub(subject, pos + strlen(search));
        subject = before + replace + after;
        lastpos = pos + strlen(replace);
    }
    return subject;
}


void dbSearch(string url,string q) {
  int i;
  string lines[];
  string items[];
  string myitems;
  string data;
  string line;

  //q = str_replace("-","%25",q);
  url += q;

  // alert(url);

  if (netget(data,url) >= 0) {
    // data = str_replace(q,"<b>"+q+"</b>",data);
    strsplit(lines, data, '\n');
    i = 0;
    for(;;) {
        if (strlen(lines[i])==0) {
          break;
        }
        strsplit(items,lines[i],'\t');
        sprintf(line,"%-4s %-20s %-10s %-40s %-15s\n",items[1],strsub(items[2],0,20),strsub(items[3],0,10),strsub(items[4],0,40),items[0]);
        myitems += line;
        i++;
    }
    alert("<pre>"+myitems);
  }
}


string q = argv[1];
if (strlen(argv[2])) {
  q += "%25"+argv[2];
}
if (strlen(argv[3])) {
  q += "%25"+argv[3];
}
if (strlen(argv[4])) {
  q += "%25"+argv[4];
}
dbSearch("http://"+DBHOST+"/list.php?action=bydesc&q=",q);
